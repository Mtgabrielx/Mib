SAMSUNG-SMARTWATCH-MIB DEFINITIONS ::= BEGIN

IMPORTS
  MODULE-IDENTITY, OBJECT-TYPE, Integer32, Unsigned32, TimeTicks, enterprises, NOTIFICATION-TYPE
    FROM SNMPv2-SMI
  DisplayString, TruthValue, DateAndTime, MacAddress
    FROM SNMPv2-TC
  MODULE-COMPLIANCE, OBJECT-GROUP, NOTIFICATION-GROUP
    FROM SNMPv2-CONF;

samsungSmartwatchMIB MODULE-IDENTITY
  LAST-UPDATED "202510120000Z"
  ORGANIZATION "IoT/Smartwatch"
  CONTACT-INFO
    "Dupla: Gabriel Dos Reis ; Joao Lucas Oliveira"
  DESCRIPTION
    "MIB didatica para um smartwatch Samsung, contendo objetos escalares
     de identificacao, saude, atividade, sistema e conectividade."
  REVISION "202510120000Z"
  DESCRIPTION "Versao inicial."
::= { enterprises 508342 }

swsModules        OBJECT IDENTIFIER ::= { samsungSmartwatchMIB 1 }
swsObjects        OBJECT IDENTIFIER ::= { samsungSmartwatchMIB 2 }
swsNotifications  OBJECT IDENTIFIER ::= { samsungSmartwatchMIB 3 }
swsConformance    OBJECT IDENTIFIER ::= { samsungSmartwatchMIB 4 }

swsDevice OBJECT IDENTIFIER ::= { swsObjects 1 }
swsHealth OBJECT IDENTIFIER ::= { swsObjects 2 }
swsActivity OBJECT IDENTIFIER ::= { swsObjects 3 }
swsSystem OBJECT IDENTIFIER ::= { swsObjects 4 }
swsConn OBJECT IDENTIFIER ::= { swsObjects 5 }

-- ====================================
--           Device Group
-- ====================================

swsName OBJECT-TYPE
  SYNTAX      DisplayString (SIZE(1..64))
  MAX-ACCESS  read-write
  STATUS      current
  DESCRIPTION
    "Nome do dispositivo"
::= { swsDevice 1 }

swsSerialNumber OBJECT-TYPE
  SYNTAX      DisplayString (SIZE(1..64))
  MAX-ACCESS  read-only
  STATUS      current
  DESCRIPTION
    "Numero de serie do dispositivo"
::= { swsDevice 2 }

swsLastBootTime OBJECT-TYPE
  SYNTAX      DateAndTime
  MAX-ACCESS  read-only
  STATUS      current
  DESCRIPTION
    "Ultimo boot (reinicializacao)"
::= { swsDevice 3 }

swsBatteryLevel OBJECT-TYPE
  SYNTAX      Unsigned32 (0..100)
  UNITS       "percent"
  MAX-ACCESS  read-only
  STATUS      current
  DESCRIPTION
    "Nivel de bateria atual em porcentagem"
::= { swsDevice 4 }

swsBatteryStatus OBJECT-TYPE
  SYNTAX      INTEGER { discharging(1),
                        charging(2),
                        full(3)
                      }
  MAX-ACCESS  read-only
  STATUS      current
  DESCRIPTION
    "Estado da bateria:
     1 - Descarregando
     2 - Carregando
     3 - Carregado
  "
::= { swsDevice 5 }


-- ====================================
--           Health Group
-- ====================================

swsHeartRateCurrent OBJECT-TYPE
  SYNTAX      Integer32 (0..300)
  UNITS       "batidas por minuto"
  MAX-ACCESS  read-only
  STATUS      current
  DESCRIPTION
    "Frequencia cardiaca atual (bpm)"
::= { swsHealth 1 }

swsStressLevel OBJECT-TYPE
  SYNTAX      INTEGER { relaxado(1),
                        baixo(2),
                        moderado(3),
                        alto(4)
                      }
  MAX-ACCESS  read-only
  STATUS      current
  DESCRIPTION
    "Nivel de estresse estimado
       1 - Relaxado
       2 - Baixo
       3 - Moderado
       4 - Alto
    "
::= { swsHealth 2 }

swsSleepDuration OBJECT-TYPE
  SYNTAX      TimeTicks
  MAX-ACCESS  read-only
  STATUS      current
  DESCRIPTION
    "Duracao do sono em time ticks (centesimos de segundos)"
::= { swsHealth 3 }

swsWaterIntakeCupsToday OBJECT-TYPE
  SYNTAX      Unsigned32
  UNITS       "mL"
  MAX-ACCESS  read-write
  STATUS      current
  DESCRIPTION
    "Quantidade de copos de agua ingeridos no dia a dia"
::= { swsHealth 4 }

swsFallDetected OBJECT-TYPE
  SYNTAX      TruthValue
  MAX-ACCESS  read-only
  STATUS      current
  DESCRIPTION
    "Estado do sensor de queda: true(1); false(2) indica ausencia
     de evento."
::= { swsHealth 5 }

-- ====================================
--           Activity Group
-- ====================================

swsStepsToday OBJECT-TYPE
  SYNTAX      Unsigned32
  MAX-ACCESS  read-only
  STATUS      current
  DESCRIPTION
    "Total de passos no decorrer do dia"
::= { swsActivity 1 }

swsActiviteMinutesToday OBJECT-TYPE
  SYNTAX      TimeTicks
  MAX-ACCESS  read-only
  STATUS      current
  DESCRIPTION
    "Tempo de atividade fisica acumulados durante o dia"
::= { swsActivity 2 }

swsCaloriesToday OBJECT-TYPE
  SYNTAX      Unsigned32
  UNITS       "Kcal"
  MAX-ACCESS  read-only
  STATUS      current
  DESCRIPTION
    "Total de calorias gastas no decorrer do dia"
::= { swsActivity 3 }

-- ====================================
--           System Group
-- ====================================

swsDndMode OBJECT-TYPE
  SYNTAX      TruthValue
  MAX-ACCESS  read-write
  STATUS      current
  DESCRIPTION
    "Modo nao pertube: true(1) = ligado, false(2) = desligado."
  DEFVAL { 2 }
::= { swsSystem 1 }

swsGoodNightMode OBJECT-TYPE
  SYNTAX      TruthValue
  MAX-ACCESS  read-write
  STATUS      current
  DESCRIPTION
    "Modo boa noite, silencia notificacoes enquanto dorme: true(1) = ligado, false(2) = desligado."
  DEFVAL { 2 }
::= { swsSystem 2 }

swsWaterLockMode OBJECT-TYPE
  SYNTAX      TruthValue
  MAX-ACCESS  read-write
  STATUS      current
  DESCRIPTION
    "Modo Bloqueio de agua (Desativa toques acidentais): true(1) = ligado, false(2) = desligado."
  DEFVAL { 2 }
::= { swsSystem 3 }

swsVibrationEnabled OBJECT-TYPE
  SYNTAX      TruthValue
  MAX-ACCESS  read-write
  STATUS      current
  DESCRIPTION
    "Vibracao habilitada para alertas e notificacoes: true(1) = ligado, false(2) = desligado."
  DEFVAL { 2 }
::= { swsSystem 4 }

swsBrightnessLevel OBJECT-TYPE
  SYNTAX      Integer32 (1..10)
  MAX-ACCESS  read-write
  STATUS      current
  DESCRIPTION
    "Nivel do brilho da tela (1 a 10)"
::= { swsSystem 5 }

-- ====================================
--           Connection Group
-- ====================================

swsBluetoothState OBJECT-TYPE
  SYNTAX      INTEGER { disconnected(1),
                        connected(2)
                      }
  MAX-ACCESS  read-write
  STATUS      current
  DESCRIPTION
    "Estado da conexao bluetooth: Discconected(1) ou Connected(2)"
::= { swsConn 1 }

swsBluetoothAddress OBJECT-TYPE
  SYNTAX      MacAddress
  MAX-ACCESS  read-only
  STATUS      current
  DESCRIPTION
    "Endereco MAC de bluetooth do smartwatch"
::= { swsConn 2 }

swsFindMyPhone OBJECT-TYPE
  SYNTAX      TruthValue
  MAX-ACCESS  read-write
  STATUS      current
  DESCRIPTION
    "Permite acionar o: encontre meu telefone a partir do relogio"
::= { swsConn 3 }

swsFindMyPhoneTriggerState OBJECT-TYPE
  SYNTAX      TruthValue
  MAX-ACCESS  accessible-for-notify
  STATUS      current
  DESCRIPTION
    "Estado do ultimo disparo de 'Encontrar meu telefone':
     true(1) indica que o evento foi acionado recentemente; o agente pode
     limpar para false(2) apos um tempo."
::= { swsConn 4 }

-- ====================================
--           Notifications
-- ====================================

swsFindMyPhoneTriggered NOTIFICATION-TYPE
 OBJECTS { swsFindMyPhoneTriggerState }
  STATUS      current
  DESCRIPTION
    "Evento do recurso 'Encontrar meu telefone' acionado a partir do relogio."
::= { swsNotifications 1 }

swsBatteryLow NOTIFICATION-TYPE
  OBJECTS { swsBatteryLevel }
  STATUS      current
  DESCRIPTION
    "Alerta de bateria baixa. Recomenda-se emitir quando o nivel de
     bateria cair para um limiar configurado."
::= { swsNotifications 2 }

swsBluetoothStateChange NOTIFICATION-TYPE
  OBJECTS { swsBluetoothState }
  STATUS      current
  DESCRIPTION
    "Mudanca de estado do Bluetooth (conectado/desconectado)."
::= { swsNotifications 3 }

swsFallEvent NOTIFICATION-TYPE
  OBJECTS { swsFallDetected }
  STATUS  current
  DESCRIPTION
    "Notificacao emitida quando o algoritmo de deteccao identifica uma queda.
     Recomenda-se enviar imediatamente e, opcionalmente, repetir como INFORM
     confiavel. O campo swsFallDetected deve estar em true(1) quando a trap
     for gerada."
::= { swsNotifications 4 }

swsBasicGroup OBJECT-GROUP
  OBJECTS {
    swsName,
    swsSerialNumber,
    swsLastBootTime,
    swsBatteryLevel,
    swsBatteryStatus,
    swsHeartRateCurrent,
    swsStressLevel,
    swsSleepDuration,
    swsWaterIntakeCupsToday,
    swsStepsToday,
    swsActiviteMinutesToday,
    swsCaloriesToday,
    swsFallDetected,
    swsDndMode,
    swsGoodNightMode,
    swsWaterLockMode,
    swsVibrationEnabled,
    swsBrightnessLevel,
    swsBluetoothState,
    swsBluetoothAddress,
    swsFindMyPhone,
    swsFindMyPhoneTriggerState
  }
  STATUS      current
  DESCRIPTION
    "Grupo basico que reune um objeto de cada categoria principal:
     Device, Health, Activity, System e Connection."
::= { swsConformance 1 }

swsNotificationGroup NOTIFICATION-GROUP
  NOTIFICATIONS {
    swsFindMyPhoneTriggered,
    swsBatteryLow,
    swsBluetoothStateChange, 
    swsFallEvent
  }
  STATUS      current
  DESCRIPTION
    "Conjunto de notificacoes que o smartwatch envia automaticamente para o gerente."
::= { swsConformance 2 }

swsBasicCompliance MODULE-COMPLIANCE
  STATUS      current
  DESCRIPTION
    "Conformidade minima para o modulo SAMSUNG-SMARTWATCH-MIB.
     Para estar em conformidade, o agente deve implementar todos
     os objetos do grupo basico."
  MODULE
    MANDATORY-GROUPS { swsBasicGroup }
    GROUP           swsNotificationGroup 
      DESCRIPTION   "Recomendado para emissao de traps/notifications."
::= { swsConformance 3 }

END
